FooBar {1 2 0 0 6 1} DEFINITIONS ::=
  BEGIN
    T3 ::= 
      SEQUENCE {
        first  INTEGER (0..65535),
        second INTEGER (0..65535),
	nest1 SEQUENCE {
	  third  INTEGER (0..65535),
	  fourth INTEGER (0..65535),
	  nest2 SEQUENCE {
	    fifth INTEGER (0..65535),
	    sixth INTEGER (0..65535)
	  }
	}
      }
  END
