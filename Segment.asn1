FooBar {1 2 0 0 6 1} DEFINITIONS ::=
  BEGIN
    T1 ::= 
      SEQUENCE {
	first BIT STRING (SIZE (0..65537))
      }
   T3 ::=
      INTEGER
   T4 ::=
      INTEGER (T3,...)
   T5 ::=
      INTEGER(...,)
  END
