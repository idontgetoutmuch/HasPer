FooBar {1 2 0 0 6 1} DEFINITIONS ::=
   BEGIN
      T1 ::= INTEGER (3)
      T2 ::= INTEGER
      T3 ::= INTEGER (3) (T2)
      T4 ::= INTEGER (3) (INTEGER)
      T5 ::= INTEGER (3) (INTEGER (3))
      T6 ::= INTEGER (3..6)
      T7 ::= INTEGER (3..6) (4..5)
      T8 ::= BIT STRING (SIZE (32))
      T9 ::= BIT STRING (SIZE (0..31))
      T10 ::= BIT STRING (SIZE (INCLUDES T1))
      T10 ::= BIT STRING (SIZE (T1))
      T11 ::= NumericString (FROM ("2"))
      T12 ::= NumericString (FROM (("4")|("2")))
   END
   
FooBaz {1 2 0 0 6 3} DEFINITIONS ::=
   BEGIN
      T1 ::= INTEGER (25..30)
      Test1 ::=
         SEQUENCE {
            first  T1,
            second T1
         }
   END

FooBaz {1 2 0 0 6 2} DEFINITIONS ::=
   BEGIN
      T1 ::= INTEGER (3)
      T2 ::= INTEGER
      T3 ::= INTEGER (3) (T2)
      T4 ::= INTEGER (3) (INTEGER)
      T5 ::= INTEGER (3) (INTEGER (3))
      T6 ::= INTEGER (3..6)
      T7 ::= INTEGER (3..6) (4..5)
      T8 ::= BIT STRING (SIZE (32))
      T9 ::= BIT STRING (SIZE (0..31))
      T10 ::= BIT STRING (SIZE (INCLUDES T1))
      T11 ::= NumericString (FROM ("2"))
      T12 ::= NumericString (FROM ("4"|"2"))
      T13 ::= INTEGER (40|50)
      T14 ::= INTEGER (25..30)
      T15 ::= INTEGER (T13|T14)
      T16 ::= INTEGER (2|4|6|8|10)
      T17 ::= IA5String (SIZE (INCLUDES T16))
      T18 ::= OCTET STRING (SIZE (1..MAX))
      T19a ::= IA5String (FROM ("AB")^SIZE (1..2))
      T19b ::= IA5String (FROM ("DE")^SIZE (3))
      T19c ::= IA5String (FROM ("ABDF")^SIZE (4..5))
      T19f ::= IA5String (FROM ("AB"))
      T19 ::= IA5String (FROM ("AB")^SIZE (1..2)
                        |FROM ("DE")^SIZE (3)
                        |FROM ("ABDF")^SIZE (4..5))
      T20 ::= T2 (3..15)
      Two ::= INTEGER (2)
      Exactly31BitsString ::= BIT STRING (SIZE (31))
      StringsOf31BitsAtTheMost ::= BIT STRING (SIZE (0..31))
      Dna ::= PrintableString (FROM ("TAGC"))
      SmallSeq ::= Dna (SIZE (10))
      CapitalAndSmall ::= PrintableString (FROM ("A".."Z"|"a".."z"))
      CapitalOrSmall ::= PrintableString (FROM ("A".."Z")|FROM ("a".."z"))
      ExoticString ::= PrintableString (SIZE (1..4)|FROM ("abc"))
      MyInteger ::= INTEGER (INTEGER) (INTEGER)
      My-type ::= 
         SEQUENCE {
            first-item  T6,
            second-item T7
         }
      EmptySeq ::=
         SEQUENCE {
         }   
   END
